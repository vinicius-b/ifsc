Mensagem DEFINITIONS AUTOMATIC TAGS ::=
BEGIN

Publish ::= SEQUENCE {
	subject OBJECT IDENTIFIER,
	value BOOLEAN
}

Subscribe ::= SEQUENCE {
	id OBJECT IDENTIFIER,	
	subject OBJECT IDENTIFIER
}

Unsubscribe ::= SEQUENCE {
	id OBJECT IDENTIFIER,	
	subject OBJECT IDENTIFIER
}

Notify ::= SEQUENCE {
	subject OBJECT IDENTIFIER,
	value BOOLEAN
}

Mensagem ::= SEQUENCE {
  msg CHOICE {
  	pub Publish,
		sub Subscribe,
		un Unsubscribe,
		noty Notify 
  }
}

END
